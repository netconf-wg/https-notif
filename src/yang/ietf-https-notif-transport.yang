module ietf-https-notif-transport {
  yang-version 1.1;
  namespace "urn:ietf:params:xml:ns:yang:ietf-https-notif-transport";
  prefix "hnt";

  import ietf-inet-types {
    prefix inet;
    reference
      "RFC 9911: Common YANG Data Types.";
  }

  import ietf-x509-cert-to-name {
    prefix x509c2n;
    reference
      "RFC 7407: YANG Data Model for SNMP Configuration.";
  }

  import ietf-subscribed-notifications {
    prefix sn;
    reference
      "RFC 8639: Subscription to YANG Notifications";
  }

  import ietf-subscribed-notif-receivers {
    prefix snr;
    reference
      "RFC XXXX: An HTTPS-based Transport for YANG Notifications.";
  }

  import ietf-yang-structure-ext {
    prefix sx;
    reference
      "RFC 8791: YANG Data Structure Extensions.";
  }

  import ietf-http-client {
    prefix httpc;
    reference
      "RFC YYYY: YANG Groupings for HTTP Clients and HTTP Servers.";
  }

  organization
    "IETF NETCONF Working Group";

  contact
    "WG Web:   <http://datatracker.ietf.org/wg/netconf>
     WG List:  <netconf@ietf.org>

     Authors: Mahesh Jethanandani (mjethanandani at gmail dot com)
              Kent Watsen (kent plus ietf at watsen dot net)";

  description
    "This YANG module is implemented by Publishers that implement
     the 'ietf-subscribed-notifications' module defined in RFC 8639.

     This module augments a 'case' statement called 'https' into
     the 'choice' statement called 'transport-type' defined
     by the 'ietf-https-notif-transport' module defined in RFC XXXX.

     Copyright (c) 2024 IETF Trust and the persons identified as
     authors of the code.  All rights reserved.
     Redistribution and use in source and binary forms, with or
     without modification, is permitted pursuant to, and subject
     to the license terms contained in, the Revised BSD
     License set forth in Section 4.c of the IETF Trust's Legal
     Provisions Relating to IETF Documents
     (http://trustee.ietf.org/license-info).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision "YYYY-MM-DD" {
    description
      "Initial Version.";
    reference
      "RFC XXXX: An HTTPS-based Transport for YANG Notifications.";
  }

  feature receiver-identity {
    description
      "Indicates that the server supports filtering notifications
       based on the receiver's identity derived from its TLS
       certificate.";
  }

  identity https {
    base sn:transport;
    base sn:configurable-encoding;
    description
      "HTTPS transport for notifications.";
  }

  grouping https-receiver-grouping {
    description
      "A grouping that may be used by other modules wishing to
       configure HTTPS-based notifications without using RFC 8639.";
    container capabilities-endpoint {
      uses httpc:http-client-grouping;
      description
        "Defines 'capabilities' resource endpoint.";
    }

    container relay-notification-endpoint {
      uses httpc:http-client-grouping;
      description
        "Defines 'relay-notification' resource endpoint.";
    }

    container receiver-identity {
      if-feature receiver-identity;
      description
        "Maps the receiver's TLS certificate to a local identity
         enabling access control to be applied to filter out
         notifications that the receiver may not be authorized
         to view.";
      container cert-maps {
        uses x509c2n:cert-to-name;
        description
          "The cert-maps container is used by a TLS-based HTTP
           server to map the HTTPS client's presented X.509
           certificate to a 'local' username. Specifically, the
           'name' field within the module is used along with
           'specified' identity to perform the match. If no
           matching and valid cert-to-name list entry is found,
           the publisher MUST close the connection, and MUST
           NOT send any notifications over it.";
        reference
          "RFC 7407: A YANG Data Model for SNMP Configuration.";
      }
    }
  }

  augment "/sn:subscriptions/snr:receiver-instances/" +
          "snr:receiver-instance/snr:transport-type" {
    case https {
      container https-receiver {
        description
          "The HTTPS receiver to send notifications to.";
        uses https-receiver-grouping;
      }
    }
    description
      "Augment the transport-type choice to include the 'https'
       transport.";
  }

  sx:structure receiver-capabilities {
    description
      "A structure defining the response body for the GET request
       to the 'capabilities' resource.  Using standard YANG
       encoding rules, when encoded as 'application/yang-data+xml'
       the root element is 'receiver-capabilities' in the namespace
       of this module, and when encoded as
       'application/yang-data+json' the top-level key is
       'ietf-https-notif-transport:receiver-capabilities'.";
    leaf-list receiver-capability {
      type inet:uri;
      description
        "A capability supported by the receiver.  A partial list
         of capabilities is defined in the 'Capabilities for HTTPS
         Notification Receivers' registry (RFC XXXX).  Additional
         custom capabilities MAY be defined.";
    }
  }
}
