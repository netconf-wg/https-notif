module example-custom-module {
  yang-version 1.1;
  namespace "http://example.com/example-custom-module";
  prefix "custom";

  import ietf-https-notif-transport {
    prefix "hnt";
    reference
      "RFC XXXX: An HTTPS-based Transport for YANG Notifications.";
  }

  organization
    "Example, Inc.";

  contact
    "Support at example.com";
  
  description
    "Example of module not using Subscribed Notifications module.";
  
  revision "YYYY-MM-DD" {
    description
      "Initial Version.";
    reference
      "RFC XXXX: An HTTPS-based Transport for YANG Notifications.";
  }

  container example-module {
    description
      "Example of using HTTPS notif without having to
       implement Subscribed Notifications.";

    container https-receivers {
      description
        "A container of all HTTPS notif receivers.";
      list https-receiver {
        key "name";
        description
          "A list of HTTPS notif receivers.";
        leaf name {
          type string;
          description
            "A unique name for the https-notif receiver.";
        }
        uses hnt:https-receiver-grouping;
      }
    }
  }
}
