module ietf-notif-receiver-https {
  yang-version 1.1;
  namespace "urn:ietf:params:xml:ns:yang:ietf-notif-receiver-https";
  prefix "nrh";

  organization
    "IETF NETCONF Working Group";

  contact
    "WG Web:   <http://tools.ietf.org/wg/netconf>
     WG List:  <netconf@ietf.org>

     Authors: Mahesh Jethanandani (mjethanandani at gmail dot com)
              Kent Watsen (kent plus ietf at watsen dot net)";

  description
    "This YANG module is implemented by Receivers to receive
     notifications via HTTPS, as described by RFC XXXX.

     This module defines a top-level 'config false' node called
     'capabilities' and an RPC called 'relay-notification'.

     These two nodes are used by Publishers in order to determine
     what optional notification-sending capbilities are supported
     by Receivers, as well as to send notifications to the
     Receivers.

     Copyright (c) 2021 IETF Trust and the persons identified as
     the document authors.  All rights reserved.
     Redistribution and use in source and binary forms, with or
     without modification, is permitted pursuant to, and subject
     to the license terms contained in, the Simplified BSD
     License set forth in Section 4.c of the IETF Trust's Legal
     Provisions Relating to IETF Documents
     (http://trustee.ietf.org/license-info).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision "YYYY-MM-DD" {
    description
      "Initial Version.";
    reference
      "RFC XXXX, YANG Data Module for HTTPS Notifications.";
  }

  /**************/
  /*  Features  */
  /**************/

  feature xml-encoding {
    description
      "Indicates that XML encoding is supported.";
  }


  /****************/
  /*  Identities  */
  /****************/

  identity capability {
    description
      "Base identity for receiver capabilities.";
  }

  identity json-encoding {
    base capability;
    description
      "Identifies support for JSON encoding.";
  }

  identity xml-encoding {
    if-feature "xml-encoding";
    base capability;
    description
      "Identifies support for XML encoding.";
  }


  /*******************************/
  /*  Protocol-accessible Nodes  */
  /*******************************/

  container receiver-capabilities {
    config false;
    description
      "A container for a list of capabilities supported by
       the Receiver.";
    leaf-list receiver-capablity {
      type identityref {
        base "nrh:capability";
      }
      description
        "A capability supported by the Receiver.";
    }
  }

  rpc relay-notification {
    description
      "An RPC for relaying a single 'notification',
       i.e., as defined by a 'notification' statement
       in a YANG module.

       In the case of an error, the RPC MUST return
       the 'ietf-restconf:errors' structure defined
       in Section 7.1 in RFC 8040.";
    input {
      anydata notification;
    }
  }

}
